FME workspace cad-upload.fmw

Parameters:
- SourceDataset_TEXTLINE = C:\safegit\fmepedia-validation\fme\data\notification.txt   # Source Text File(s)
- EMAIL_TYPE = direct   # Email type

Readers:
- TEXTLINE_1: TEXTLINE from $(SourceDataset_TEXTLINE)

StringReplacer
    FIND_TEXT = "
    NO_MATCH = _FME_NO_OP_
    CASE = no
    REGEXP = no
    SRC_ATTRS = email_publisher_attachment{0}
    -> FMEServerJobSubmitter
FMEServerJobSubmitter
    SUBSECTION = SERVER_JOB_SUBMITTER
    PRIORITY = 100
    BLOCKING = Yes
    SERVER_NAME = http://myfmeserver
    DATASET_OVERRIDE = YES
    USERNAME = author
    WORKSPACE_NAME = validate-subworkspace.fmw
    WORKSPACE_PARAMETERS = SourceDataset_ACAD,@Value(email_publisher_attachment{0})
    SERVER_PORT = 0
    PASSWORD =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
    REPOSITORY = validation
    SUCCEEDED -> AttributeFileReader
AttributeFileReader
    DEST_ATTR = _file_contents
    CHAR_ENCODING = utf-8
    FILE_NAME = @Value(output_datasets{1}.path)
    -> FilenamePartExtractor
FilenamePartExtractor
    SRC_ATTR = @Value(email_publisher_attachment{0})
    FULLNAME_ATTR = submitted_file
    -> Tester_2
Tester_2
    TEST_DESCRIPTION = ""
    TEST_CLAUSE = TEST @Value(_file_contents) NOT_CONTAINS FAILED
    BOOL_OP = OR
    TEST_MODE = Automatic
    PASSED -> AttributeCreator
    FAILED -> AttributeCreator_2
AttributeCreator
    ATTR_LIST = topic,cad_waterqa_success,subject,QA for file @Value(submitted_file) succeeded!,message,File @Value(submitted_file) has been loaded into the central repository database.
    -> FMEServerEmailGenerator
AttributeCreator_2
    ATTR_LIST = topic,cad_waterqa_failure,subject, QA for file @Value(submitted_file) failed!,message,File @Value(submitted_file) has errors and therefore has NOT been loaded into the central repository database. See the attached HTML file for details of the errors.
    -> FMEServerEmailGenerator
FMEServerEmailGenerator
    email_subject = @Value(subject)
    email_subscriber_content = @Value(message)
    email_attachment_paths = @Value(output_datasets{1}.path)
    email_to = @Value(email_publisher_from)
    -> Tester_3
Tester_3
    TEST_DESCRIPTION = ""
    TEST_CLAUSE = TEST @Value(topic) CONTAINS success
    BOOL_OP = OR
    TEST_MODE = Automatic
    PASSED -> FMEServerNotifier
    FAILED -> FMEServerNotifier_2
Note: Edit to configure for your server. / Can't link to user parameters (PR#57432)
FMEServerNotifier
    BODY = @Value(text_line_data)
    USERNAME = author
    URL = http://myfmeserver
    TOPIC = cad_waterqa_success
    PASSWORD =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
Note: Edit to configure for your server. / Can't link to user parameters (PR#57432)
FMEServerNotifier_2
    BODY = @Value(text_line_data)
    USERNAME = author
    URL = http://myfmeserver
    TOPIC = cad_waterqa_failure
    PASSWORD =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

Bookmark: Parse email notification
text_line (reader TEXTLINE_1)
    attributes: text_line_data buffer
    -> JSONFlattener
JSONFlattener
    RECURSIVE = Yes
    JSON_ATTR = text_line_data
    -> Tester
Tester
    TEST_DESCRIPTION = ""
    TEST_CLAUSE = TEST $(EMAIL_TYPE) = imap
    BOOL_OP = OR
    TEST_MODE = Automatic
    PASSED -> AttributeExposer_2
    FAILED -> AttributeExposer
AttributeExposer_2
    ATTR_LIST = imap_publisher_attachment{},imap_publisher_to,imap_publisher_received,imap_publisher_subject,imap_publisher_from,imap_publisher_sent
    -> BulkAttributeRenamer
BulkAttributeRenamer
    REPLACE_STR = email
    ATTRCHOICE = All Attributes
    PATTERN_ACTION_DISP = String Replace
    REPLACE_PATTERN = imap
    CASE_DISP = yes
    -> StringReplacer
AttributeExposer
    ATTR_LIST = email_publisher_attachment{},email_publisher_to,email_publisher_received,email_publisher_subject,email_publisher_from,email_publisher_sent
    -> StringReplacer

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_to =   # To
- email_cc =   # CC
- email_from =   # From
- email_replyto =   # Reply to
- email_subject =   # Subject
- email_subscriber_content =   # Message
- email_attachment_paths =   # Attachments (comma separated)

INPUT (input)
    -> Counter
Counter
    CNT_ATTR = _email_feature_id
    SCOPE = Local
    DOMAIN = counter
    START = 0
    -> ParameterFetcher
ParameterFetcher
    ATTR_LIST = _email_from {$(email_from)} _email_replyto {$(email_replyto)} _email_attachment_paths {$(email_attachment_paths)} _email_cc {$(email_cc)}
    -> AttributeCreator
AttributeCreator
    NUM_PRIOR_FEATURES = 0
    ATTR_LIST = _email_to,$(email_to),_email_subject,$(email_subject),_email_subscriber_content,$(email_subscriber_content)
    NUM_SUBSEQUENT_FEATURES = 0
    -> JSONTemplater
JSONTemplater
    RESULT_ATTRIBUTE = text_line_data
    VISIBLE_QUERY_VALIDATE = Yes
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    CONSECUTIVE_GROUPS = No
    -> Tester
Tester
    TEST_DESCRIPTION = ""
    TEST_CLAUSE = TEST _email_attachment_paths ATTRIBUTE_IS_EMPTY <Unused>
    BOOL_OP = OR
    TEST_MODE = Automatic
    PASSED -> OUTPUT (output)
    FAILED -> AttributeSplitter
OUTPUT (output)

Bookmark: Add the attachments
AttributeSplitter
    ATTR_NAME = _email_attachment_paths
    DROP_EMPTY_PARTS = No
    DELIMITER = ,
    TRIM_OPTION = Both
    LIST_NAME = _email_attachment_path_list
    -> ListExploder
ListExploder
    LIST_ATTR = _email_attachment_path_list{}
    INDEX_ATTR = _element_index
    MODE = List Elements and Original Attributes
    LIST_FOUND -> StringConcatenator
StringConcatenator
    PARM_LINE = "email_attachment{@Value(_element_index)}": "@Value(_email_attachment_path_list)"
    VAL_ATTR = _email_attachment_json
    -> Aggregator
Aggregator
    AGGREGATE_TYPE = Homogeneous Collection (If Possible)
    CONCAT_ATTRS = _email_attachment_json
    ACCUM_ATTRS_NAME = Yes
    MODE = Assemble One Level
    SEP = ,
    ORDERED = No
    GROUP_BY = _email_feature_id
    AGGREGATE -> StringReplacer_2
StringReplacer_2
    FIND_TEXT = \
    NO_MATCH = _FME_NO_OP_
    REPLACE_TEXT = \\
    CASE = no
    REGEXP = no
    SRC_ATTRS = _email_attachment_json
    -> StringReplacer
StringReplacer
    FIND_TEXT = }
    NO_MATCH = _FME_NO_OP_
    REPLACE_TEXT:
      ,
      @Value(_email_attachment_json)
      }
    CASE = no
    REGEXP = no
    SRC_ATTRS = text_line_data
    -> OUTPUT (output)
