FME workspace D001 - websocket-stream.fmw

Parameters:
- type = i   # Type
- counter = 1
- minID = 0   # Minimum sequential ID
- maxID = 100   # Maximum sequential ID
- USERNAME = admin   # Username
- PASSWORD =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   # PASSWORD Password
- DATABASE = CADQA   # Postgres database
- PG_USER = postgres   # Postgres username
- PG_PASS =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   # Postgres password
- PG_SERVER = localhost   # Postgres server
- PG_PORT = 54321   # Postgres server port

SQLCreator
    POSTGIS_PORT = $(PG_PORT)
    SQL_STATEMENT:
      SELECT w.feature_id, w.geom FROM "WATERLINES" AS w, "temp_ids" AS t
      WHERE  w.feature_id = t.feature_id
      AND t.id BETWEEN $(minID) AND $(maxID);
    EXPOSED_ATTRIBUTE_LIST = feature_id
    POSTGIS_USER_NAME = $(PG_USER)
    DATASET = $(DATABASE)
    POSTGIS_HOST = $(PG_SERVER)
    POSTGIS_PASSWORD = $(PG_PASS)
    FORMAT = POSTGIS
    RESULT -> Reprojector
    RESULT -> NoFeaturesTester
Decelerator
    DECEL_TYPE = Per Feature Delay
    DELAY = 0.01
    -> WebSocketSender
WebSocketSender
    PREAMBLE:
      {
          ws_op: "open",
          ws_stream_id: "cadqa"
       }
    DATA:
      {
          ws_op: "send",
          ws_msg: @Value(_stringinsertupdate)
      }
    HOST = ws://localhost:7078/websocket
NoFeaturesTester
    INPUT -> Sampler
    NOINPUT -> Tester_2
Sampler
    RATE = 1
    SAMPLE_TYPE_LONG = First N Features
    SAMPLED -> SQLExecutor
Note: Delete Elements from temp Table
SQLExecutor
    POSTGIS_PORT = $(PG_PORT)
    SQL_STATEMENT = DELETE FROM temp_ids WHERE id BETWEEN $(minID) AND $(maxID)
    POSTGIS_USER_NAME = $(PG_USER)
    DATASET = $(DATABASE)
    POSTGIS_HOST = $(PG_SERVER)
    POSTGIS_PASSWORD = $(PG_PASS)
    COMBINE_GEOM = Initiator Geometry Only
    COMBINE_ATTRS = Result Attributes Only
    FORMAT = POSTGIS

Bookmark: Create JSON for web map
Reprojector
    DEST = EPSG:4326
    RASTER_CELL_SIZE = Preserve Cells
    STROKE_ARCS = Yes
    SOURCE = Read from feature
    INTERPOLATION_TYPE_NAME = Nearest Neighbor
    REPROJECTED -> GeometryExtractor
GeometryExtractor
    ATTR = _geometryupdated
    KIND_LONG = GeoJSON
    -> ParameterFetcher_2
ParameterFetcher_2
    ATTR_LIST = _type {$(type)}
    -> StringConcatenator_3
StringConcatenator_3
    PARM_LINE = {"id" : "@Value(feature_id)","type": "@Value(_type)","features" : [ @Value(_geometryupdated)]}
    VAL_ATTR = _stringinsertupdate
    -> Decelerator

Bookmark: Read failed so re-run this translation
Tester_2
    TEST_MODE = Automatic
    TEST_DESCRIPTION = ""
    BOOL_OP = OR
    TEST_CLAUSE = TEST "$(counter)" < "15"
    PASSED -> ExpressionEvaluator
ExpressionEvaluator
    VAL_ATTR = _result
    EXPRESSION = $(counter)+1
    -> FMEServerJobSubmitter
FMEServerJobSubmitter
    PASSWORD = $(PASSWORD)
    USERNAME = $(USERNAME)
    SERVER_NAME = http://localhost
    WORKSPACE_NAME = D001 - websocket-stream.fmw
    BLOCKING = No
    REPOSITORY = cadqa
    SERVER_PORT = 0
    WORKSPACE_PARAMETERS = type,$(type),counter,@Value(_result),minID,$(minID),maxID,$(maxID)
    SUBSECTION = SERVER_JOB_SUBMITTER
    PRIORITY = 100

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
There are no special instructions for using this transformer.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

INPUT (input)
    -> INPUT (output)
    -> Sampler
Note: Take the first input feature
Sampler
    RATE = 1
    SAMPLE_TYPE_LONG = First N Features
    SAMPLED -> StatisticsCalculator
INPUT (output)
Creator
    NUM = 1
    GEOMTYPE = Geometry Object
    CREATED -> StatisticsCalculator
Note: Count received features
StatisticsCalculator
    STATS_ATTR = no_features
    PASS_THROUGH = No
    COUNT_ATTR = NFT_count
    STATISTICS -> Tester_2
Note: If the number of features is equal / to 1, we had no feature coming / through the Input port
Tester_2
    TEST_MODE = Automatic
    TEST_DESCRIPTION = ""
    BOOL_OP = OR
    TEST_CLAUSE = TEST "@Value(NFT_count)" = "1"
    PASSED -> AttributeCreator
Note: Provide an attribute for filtering
AttributeCreator
    ATTR_LIST = no_features,true
    -> NOINPUT (output)
NOINPUT (output)
