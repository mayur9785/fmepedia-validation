FME workspace validate-subworkspace.fmw

Parameters:
- SourceDataset_ACAD = C:\safegit\fmepedia-validation\www\download\distribution_N25_bad.dwg   # Source Autodesk AutoCAD DWG/DXF File(s)

Readers:
- ACAD_1: ACAD from $(SourceDataset_ACAD) in EPSG:2277

Writers:
- TEXTLINE_1: TEXTLINE to file.html
- POSTGIS_1: POSTGIS to gisdb

water_distribution_lines (reader ACAD_1)
    attributes: ANNO_DIAM char(4), COMPKEY number(2,0), COMPTYPE number(2,0), DIAMETER number(3,0), DRAW number(2,0), FEATURE_ID char(25), LEAD_MAIN_ number(3,0), MATERIAL char(8), PROJECT char(9), PR_ZONE char(4), STATUS char(3), SYMCODE number(4,0), SYMCODE2 number(4,0), TILE char(4), WNM_TYPE char(8), YEAR_INSTA number(5,0)
    -> GeometryFilter
GeometryFilter
    GEOM_PORT_NAMES = Line
    BREAK_AGG = No
    LINE -> GeometryValidator
    LINE -> FeatureHolder
text_line (writer TEXTLINE_1)
    attributes: text_line_data buffer

Bookmark: Validation
GeometryValidator
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = No
    OGC_SIMPLE_CHECK = OGC_SIMPLE_CHECK
    OGC_VALID_CHECK = OGC_VALID_CHECK
    PRESETS = OGC
    ISSUE_ATTR_NAME = _issues
    FAILED -> VariableSetter
    PASSED -> Tester
VariableSetter
    VALUE = yes
    SCOPE = Global
    VARNAME = _invalidFeatures
    -> XMLTemplater_2
XMLTemplater_2
    VISIBLE_QUERY_VALIDATE = No
    RESULT_ATTRIBUTE = Remarks
    OUTPUT_XML_HEADER = No
    ROOT_QUERY_EXPR:
      <div style="min-width: 200px;">Invalid Geometry
      </div>
    -> AttributeCreator
Tester
    TEST_CLAUSE = TEST @Value(DIAMETER) NOT_= 0
    TEST_DESCRIPTION = ""
    BOOL_OP = OR
    TEST_MODE = Automatic
    FAILED -> VariableSetter_2
VariableSetter_2
    VALUE = yes
    SCOPE = Global
    VARNAME = _invalidFeatures
    -> XMLTemplater
XMLTemplater
    VISIBLE_QUERY_VALIDATE = No
    RESULT_ATTRIBUTE = Remarks
    OUTPUT_XML_HEADER = No
    ROOT_QUERY_EXPR:
      <div>Invalid Attribute: DIAMETER
      </div>
    -> AttributeCreator

Bookmark: Report creation
AttributeCreator
    ATTR_LIST = _invalid_features,yes
    -> GoogleStaticMapCreator
GoogleStaticMapCreator
    -> XMLTemplater_3 [input 2]
Creator
    GEOMTYPE = Geometry Object
    NUM = 1
    CREATED -> VariableRetriever_2
VariableRetriever_2
    VALUE_ATTR = _invalidFeatures
    SCOPE = Global
    VARNAME = _invalidFeatures
    -> Tester_3
Tester_3
    TEST_CLAUSE = TEST @Value(_invalidFeatures) = yes
    TEST_DESCRIPTION = ""
    BOOL_OP = OR
    TEST_MODE = Automatic
    PASSED -> XMLTemplater_3 [input 1]
XMLTemplater_3
    VISIBLE_QUERY_VALIDATE = No
    RESULT_ATTRIBUTE = _htmlTable
    OUTPUT_XML_HEADER = No
    ROW_QUERY_EXPR:
      <tr>
      <td>{fme:get-attribute("TILE")}</td>
      <td>{fme:get-attribute("FEATURE_ID")}</td>
      <td>{fme:get-attribute("DIAMETER")}</td>
      <td>{fme:get-attribute("WNM_TYPE")}</td>
      <td>{fme:get-xml-attribute("Remarks")}</td>
      <td><img src='{fme:get-attribute("_StaticMapUrl")}'></img></td>
      </tr>
    ROOT_QUERY_EXPR:
      <table>
      <tr>
      <th>TILE</th>
      <th>FEATURE_ID</th>
      <th>DIAMETER</th>
      <th>WNM_TYPE</th>
      <th>Error Remarks</th>
      <th>Map</th>
      </tr>
      {fme:process-features("ROW")}
      </table>
    -> StringConcatenator
StringConcatenator
    ACTION = Create New Attribute
    PARM_LINE:
      <!DOCTYPE html>
      <html>
      <head>
        <meta charset="utf-8">

        <!-- Use the .htaccess and remove these lines to avoid edge case issues. More info: h5bp.com/i/378 -->
        <meta http-equiv="X-UA-Compatible" content="IE=edge,chrome=1">

        <title>Data validation failure</title>
        <meta name="description" content="">

        <!-- Mobile viewport optimized: h5bp.com/viewport -->
        <meta name="viewport" content="width=device-width">

        <!-- CSS goes in the document HEAD or added to your external stylesheet -->
          <style type="text/css">
          /* ------------------
           styling for the tables
             ------------------   */
          body {
              font-family: 'Lucida Sans Unicode', 'Lucida Grande', Sans-Serif;
          }
          table {
            line-height: 1.6em;
            font-size: 12px;
            background: #fff;
            margin: 45px;
            width: 480px;
            border-collapse: collapse;
            text-align: left;
          }

          th {
            font-size: 14px;
            font-weight: normal;
            color: #039;
            padding: 10px 8px;
            border-bottom: 2px solid #6678b1;
          }

          tr {
            color: #669;
            padding: 9px 8px 0px 8px;
          }

          </style>

      </head>
      <body>

      <h1>Validation FAILED</h1>
      @Value(_htmlTable)

      </body>
      </html>
    VAL_ATTR = text_line_data
    -> text_line (writer TEXTLINE_1)

Bookmark: Data loader
FeatureHolder
    -> VariableRetriever
VariableRetriever
    VALUE_ATTR = _invalidFeatures
    SCOPE = Global
    VARNAME = _invalidFeatures
    -> Tester_2
Tester_2
    TEST_CLAUSE = TEST @Value(_invalidFeatures) NOT_= yes
    TEST_DESCRIPTION = ""
    BOOL_OP = OR
    TEST_MODE = Automatic
    PASSED -> Sampler
    PASSED -> AttributeCreator_3
BulkAttributeRenamer_2
    ATTRCHOICE = All Attributes
    PATTERN_ACTION_DISP = Change Case
    CASE_CHANGE_TYPE = lowercase
    -> cad_qa.WATERLINES (writer POSTGIS_1)
cad_qa.WATERLINES (writer POSTGIS_1)
    attributes: anno_diam varchar(255), compkey numeric(38,0), comptype numeric(38,0), diameter varchar(255), draw numeric(38,0), feature_id varchar(25), lead_main_ numeric(38,0), material varchar(8), primaryindex numeric(38,0),PRIKEY, project varchar(255), pr_zone varchar(4), status varchar(3), symcode numeric(38,0), symcode2 numeric(38,0), tile varchar(4), wnm_type varchar(8), year_insta numeric(38,0), autocad_elevation numeric(38,0), bulk_load numeric(38,0)

Bookmark: DELETE
Sampler
    RATE = 1
    SAMPLE_TYPE_LONG = First N Features
    SAMPLED -> AttributeCreator_2
AttributeCreator_2
    ATTR_LIST = fme_db_operation,DELETE,fme_where,tile='N25'
    -> BulkAttributeRenamer_2

Bookmark: INSERT
AttributeCreator_3
    ATTR_LIST = fme_db_operation,INSERT
    -> FeatureHolder_2
FeatureHolder_2
    -> Counter
Counter
    CNT_ATTR = primaryindex
    SCOPE = Global
    START = 1
    DOMAIN = _primaryindex
    -> BulkAttributeRenamer_2
    -> Aggregator

Bookmark: HTML report for success
Aggregator
    ORDERED = No
    COUNT_ATTR = _count
    ACCUM_ATTRS_NAME = No
    MODE = Attributes Only
    SEP = ,
    AGGREGATE -> TimeStamper
Note: Timestamp according to locale
TimeStamper
    FMT = ^c
    TIME_ATTR = _timestamp
    -> StringConcatenator_2
StringConcatenator_2
    ACTION = Create New Attribute
    PARM_LINE:
      <!doctype html>
      <head>
        <meta charset="utf-8">

        <!-- Use the .htaccess and remove these lines to avoid edge case issues. More info: h5bp.com/i/378 -->
        <meta http-equiv="X-UA-Compatible" content="IE=edge,chrome=1">

        <title></title>
        <meta name="description" content="">

        <!-- Mobile viewport optimized: h5bp.com/viewport -->
        <meta name="viewport" content="width=device-width">


      </head>
      <body>
      <h1>Validation SUCCEEDED</h1>
          <p>Load Complete - Data Validation was Successful</p>
          <p>Date Loaded:  @Value(_timestamp)<br>
          Number of Features Added: @Value(_count)</p>
      </body>
      </html>
    VAL_ATTR = text_line_data
    -> text_line (writer TEXTLINE_1)

FME custom transformer GoogleStaticMapCreator

Input (input)
    -> Reprojector
Reprojector
    SOURCE = TX83-CF
    RASTER_CELL_SIZE = Preserve Cells
    DEST = EPSG:4326
    STROKE_ARCS = Yes
    INTERPOLATION_TYPE_NAME = Nearest Neighbor
    REPROJECTED -> CoordinateSwapper
CoordinateSwapper
    SWAP_TYPE = X <-> Y
    -> GeometryExtractor
GeometryExtractor
    ATTR = _geometry
    OGCVERSION = 1.1
    KIND_LONG = OGC Well Known Text
    -> SubstringExtractor
SubstringExtractor
    SRC_ATTR = _geometry
    END = -2
    RESULT_ATTR = _path
    START = 12
    -> StringReplacer_2
StringReplacer_2
    SRC_ATTRS = _path
    REGEXP = no
    NO_MATCH = _FME_NO_OP_
    CASE = no
    FIND_TEXT = ,
    REPLACE_TEXT = |
    -> StringReplacer
StringReplacer
    SRC_ATTRS = _path
    REGEXP = no
    NO_MATCH = _FME_NO_OP_
    CASE = no
    FIND_TEXT = " "
    REPLACE_TEXT = ,
    -> CoordinateExtractor
CoordinateExtractor
    Y_ATTR = _y
    X_ATTR = _x
    IND = 0
    Z_DEFAULT = -9999
    Z_ATTR = _z
    -> StringConcatenator_5
StringConcatenator_5
    PARM_LINE = http://maps.googleapis.com/maps/api/staticmap?center=@Value(_x),@Value(_y)&amp&amp&size=200x200&amp&sensor=false&path=color:0x0000ff|weight:5|@Value(_path)&key=AIzaSyAAJ9HjDtsSOYUzLI6Xkvfc8RMHOi6RfIs
    VAL_ATTR = _StaticMapUrl
    -> Output (output)
Output (output)
