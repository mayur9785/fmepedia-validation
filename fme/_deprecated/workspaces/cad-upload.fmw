FME workspace cad-upload.fmw
Title: CAD & GIS Workflow - 3. CAD Data Validation & Load
Description: CAD & GIS Workflow for FME Server (FME 2011)
Workspace uploads the CAD data, validates the DWG file and if validation is successful loads the DWG into the database. 
If the validation fails, an HTML report of the bad features is generated.

Parameters:
- SourceDataset_TEXTLINE = C:\safegit\fmepedia-validation\fme\data\email_content.json   # Source Text File(s)
- EMAIL_TYPE = email   # Type of email publisher

Readers:
- TEXTLINE_1: TEXTLINE from $(SourceDataset_TEXTLINE)

Logger
    MESSAGE = Feature is:
    MAXFEATS = 20
    MAXCOORDS = 20
    LOGGED -> FMEServerJobSubmitter
FMEServerJobSubmitter
    USERNAME = fmepediademos
    SERVER_NAME = https://localhost
    WORKSPACE_NAME = validate-subworkspace.fmw
    BLOCKING = Yes
    REPOSITORY = validation
    SERVER_PORT = 0
    WORKSPACE_PARAMETERS = SourceDataset_ACAD,@Value(attached_file)
    SUBSECTION = SERVER_JOB_SUBMITTER
    PRIORITY = 100
    SUCCEEDED -> AttributeFileReader
AttributeFileReader
    CHAR_ENCODING = utf-8
    FILE_NAME = @Value(output_datasets{0}.path)
    DEST_ATTR = _file_contents
    -> FilenamePartExtractor_3
FilenamePartExtractor_3
    SRC_ATTR = email_publisher_attachment{0}
    TGT_ATTR = submitted_file
    FILENAME_PART = Full Filename
    -> Tester_4
Tester_4
    TEST_MODE = Automatic
    TEST_DESCRIPTION = ""
    BOOL_OP = OR
    TEST_CLAUSE = TEST @Value(_file_contents) NOT_CONTAINS FAILED
    PASSED -> FMEServerEmailGenerator
    FAILED -> FMEServerEmailGenerator_2
FMEServerEmailGenerator
    email_subject = QA for file @Value(submitted_file) succeeded!
    email_to = @Value(email_publisher_from)
    email_from = fmeserver@gmaill.com
    email_subscriber_content = File @Value(submitted_file) has been loaded into the central repository database.
    email_attachment_paths = @Value(output_datasets{0}.path)
    -> FMEServerNotifier
FMEServerNotifier
    BODY = @Value(text_line_data)
    TOPIC = cad_waterqa_success
    URL = https://localhost
FMEServerEmailGenerator_2
    email_subject = QA for file @Value(submitted_file) failed!
    email_to = @Value(email_publisher_from)
    email_from = fmeserver@gmaill.com
    email_subscriber_content = File @Value(submitted_file) has errors and therefore has NOT been loaded into the central repository database. See the attached HTML file for details of the errors.
    email_attachment_paths = @Value(output_datasets{0}.path)
    -> FMEServerNotifier_2
FMEServerNotifier_2
    USERNAME = fmepediademos
    BODY = @Value(text_line_data)
    TOPIC = cad_waterqa_fail
    URL = https://localhost

Bookmark: Parse Email Request
text_line (reader TEXTLINE_1)
    attributes: text_line_data buffer
    -> JSONFlattener
JSONFlattener
    RECURSIVE = Yes
    JSON_ATTR = text_line_data
    -> Tester
Note: Check expected email publisher type / so we know which attributes to expose
Tester
    TEST_MODE = Automatic
    TEST_DESCRIPTION = ""
    BOOL_OP = OR
    TEST_CLAUSE = TEST $(EMAIL_TYPE) = imap
    PASSED -> AttributeExposer_2
    FAILED -> AttributeExposer
AttributeExposer_2
    ATTR_LIST = imap_publisher_attachment{},imap_publisher_to,imap_publisher_received,imap_publisher_subject,imap_publisher_from,imap_publisher_sent
    -> StringReplacer
StringReplacer
    SRC_ATTRS = imap_publisher_attachment{0}
    REGEXP = no
    CASE = no
    NO_MATCH = _FME_NO_OP_
    FIND_TEXT = "
    -> AttributeRenamer
AttributeRenamer
    ATTR_LIST = imap_publisher_attachment{0},attached_file,""
    -> Logger
AttributeExposer
    ATTR_LIST = email_publisher_attachment{},email_publisher_to,email_publisher_received,email_publisher_subject,email_publisher_from,email_publisher_sent
    -> AttributeRenamer_2
AttributeRenamer_2
    ATTR_LIST = email_publisher_attachment{0},attached_file,""
    -> Logger

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_to =   # To
- email_cc =   # CC
- email_from =   # From
- email_replyto =   # Reply to
- email_subject =   # Subject
- email_subscriber_content =   # Message
- email_attachment_paths =   # Attachments (comma separated)

INPUT (input)
    -> Counter
Counter
    SCOPE = Local
    START = 0
    DOMAIN = counter
    CNT_ATTR = _email_feature_id
    -> ParameterFetcher
ParameterFetcher
    ATTR_LIST = _email_from {$(email_from)} _email_replyto {$(email_replyto)} _email_attachment_paths {$(email_attachment_paths)} _email_cc {$(email_cc)}
    -> AttributeCreator
AttributeCreator
    NUM_PRIOR_FEATURES = 0
    NUM_SUBSEQUENT_FEATURES = 0
    ATTR_LIST = _email_to,$(email_to),_email_subject,$(email_subject),_email_subscriber_content,$(email_subscriber_content)
    -> JSONTemplater
JSONTemplater
    RESULT_ATTRIBUTE = text_line_data
    CONSECUTIVE_GROUPS = No
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    VISIBLE_QUERY_VALIDATE = Yes
    -> Tester
Tester
    TEST_MODE = Automatic
    TEST_DESCRIPTION = ""
    BOOL_OP = OR
    TEST_CLAUSE = TEST _email_attachment_paths ATTRIBUTE_IS_EMPTY <Unused>
    PASSED -> OUTPUT (output)
    FAILED -> AttributeSplitter
OUTPUT (output)

Bookmark: Add the attachments
AttributeSplitter
    LIST_NAME = _email_attachment_path_list
    ATTR_NAME = _email_attachment_paths
    DELIMITER = ,
    TRIM_OPTION = Both
    DROP_EMPTY_PARTS = No
    -> ListExploder
ListExploder
    INDEX_ATTR = _element_index
    MODE = List Elements and Original Attributes
    LIST_ATTR = _email_attachment_path_list{}
    LIST_FOUND -> StringConcatenator
StringConcatenator
    PARM_LINE = "email_attachment{@Value(_element_index)}": "@Value(_email_attachment_path_list)"
    VAL_ATTR = _email_attachment_json
    -> Aggregator
Aggregator
    GROUP_BY = _email_feature_id
    MODE = Assemble One Level
    ACCUM_ATTRS_NAME = Yes
    SEP = ,
    AGGREGATE_TYPE = Homogeneous Collection (If Possible)
    CONCAT_ATTRS = _email_attachment_json
    ORDERED = No
    AGGREGATE -> StringReplacer_2
StringReplacer_2
    SRC_ATTRS = _email_attachment_json
    REGEXP = no
    CASE = no
    REPLACE_TEXT = \\
    NO_MATCH = _FME_NO_OP_
    FIND_TEXT = \
    -> StringReplacer
StringReplacer
    SRC_ATTRS = text_line_data
    REGEXP = no
    CASE = no
    REPLACE_TEXT:
      ,
      @Value(_email_attachment_json)
      }
    NO_MATCH = _FME_NO_OP_
    FIND_TEXT = }
    -> OUTPUT (output)
